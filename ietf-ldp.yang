module ietf-ldp {
  namespace "urn:ietf:params:xml:ns:yang:ietf-ldp";
  // replace with IANA namespace when assigned
  prefix ldp;

  import ietf-inet-types {
    prefix "inet";
  }
  
  import ietf-yang-types {
    prefix "yang";
  }
  
  import ietf-interfaces {
    prefix "if";
  }
  
  import ietf-ip {
    prefix "ip";
  }
  
  import ietf-routing {
    prefix "rt";
  }
  
  import routing-policy {
    prefix "rpl";
  }
  
  organization "TBD";
  contact "TBD";
  description
    "";

  revision 2015-03-05 {
    description
      "Initial revision.";
    reference
      "";
  }

  /*
   * Features
   */
  feature capability-config {
    description
      "This feature indicates that the system allows to configure
      LDP capability.";
  }

  feature global-session-authentication {
    description
      "This feature indicates that the system allows to configure
       authentication at global level.";
  }

  feature graceful-restart-helper-mode {
    description
      "This feature indicates that the system supports graceful
      restart helper mode.";
  }

  feature per-interface-timer-config {
    description
      "This feature indicates that the system allows to configure
      interface hello timers at the per-interface level.";
  }

  feature per-neighbor-graceful-restart-config {
    description
      "This feature indicates that the system allows to configure
      graceful restart at the per-neighbor level.";
  }

  feature per-neighbor-session-attributes-config {
    description
      "This feature indicates that the system allows to configure
      session attributes at the per-neighbor level.";
  }

  feature policy-extended-discovery-config {
    description
      "This feature indicates that the system allows to configure
      policies to control the acceptance of extended neighbor
      discovery hello messages.";
  }

  feature policy-label-assignment-config {
    description
      "This feature indicates that the system allows to configure
      policies to assign labels according to certain prefixes.";
  }

  feature policy-ordered-label-config {
    description
      "This feature indicates that the system allows to configure
      ordered label policies.";
  }

  feature session-protection {
    description
      "This feature indicates that the system supports session 
      protection";
  }

  /*
   * Typedefs
   */
  typedef prefix-list-ref {
    type leafref {
      path "/rpl:routing-policy/rpl:defined-sets/rpl:prefix-set/"
        +"rpl:prefix-set-name";
    }
    description
      "A type for a reference to a prefix list.";
  }

  typedef oper-status-event-type {
    type enumeration {
      enum up {
        value 1;
        description
          "Operational status changed to up.";
      }
      enum down {
        value 2;
        description
          "Operational status changed to down.";
      }
    }
    description "Operational status event type for notifications.";
  }

  /*
   * Identities
   */

  identity ldp {
    base "rt:routing-protocol";
    description "LDP";
  }

  /*
   * Groupings
   */
  grouping ldp-instance-ref {
    description
      "An absolute reference to an LDP instance.";
    leaf routing-instance-ref {
      type rt:routing-instance-ref;
      description
        "Reference to the routing instance.";
    }

    leaf ldp-ref {
      type leafref {
        path "/rt:routing/rt:routing-instance"
          + "[rt:name = current()/../routing-instance-ref]/"
          + "rt:routing-protocols/rt:routing-protocol/rt:name";
      }
      description
        "Reference to an LDP protocal name.";
    }
    leaf ldp-instance-ref {
      type leafref {
        path "/rt:routing/rt:routing-instance"
          + "[rt:name = current()/../routing-instance-ref]/"
          + "rt:routing-protocols/rt:routing-protocol"
          + "[rt:name = current()/../ldp-ref]/ldp/instance/name";
      }
      description
        "Reference to an LDP instance.";
    }
  } // ldp-instance-ref

  grouping ldp-neighbor-ref {
    description
      "An absolute reference to an LDP neighbor.";
    uses ldp-instance-ref;
    leaf neighbor-ref {
      type leafref {
        path "/rt:routing/rt:routing-instance"
          + "[rt:name = current()/../routing-instance-ref]/"
          + "rt:routing-protocols/rt:routing-protocol"
          + "[rt:name = current()/../ldp-ref]/ldp/instance"
          + "[name = current()/../ldp-instance-ref]/neighbors/"
          + "neighbor/lsr-id";
      }
      description
        "Reference to an LDP neighbor.";
    }
  } // ldp-neighbor-ref

  grouping ldp-interface-ref {
    description
      "An absolute reference to an LDP interface.";
    uses ldp-instance-ref;
    leaf interface-ref {
      type leafref {
        path "/rt:routing/rt:routing-instance"
          + "[rt:name = current()/../routing-instance-ref]/"
          + "rt:routing-protocols/rt:routing-protocol"
          + "[rt:name = current()/../ldp-ref]/ldp/instance"
          + "[name = current()/../ldp-instance-ref]/discovery/"
          + "interfaces/interface/interface";
      }
      description
        "Reference to an LDP interface.";
    }
  } // ldp-interface-ref

  grouping basic-discovery-timers {
    description
      "Basic discovery timer attributes.";
    leaf hello-holdtime {
      type uint16 {
        range 15..3600;
      }
      units seconds;
      default 15;
      description
        "The time interval for which a LDP link Hello adjacency
        is maintained in the absence of link Hello messages from
        the LDP neighbor";
    }
    leaf hello-interval {
      type uint16 {
        range 5..1200;
      }
      units seconds;
      default 5;
      description
        "The interval between consecutive LDP link Hello messages
        used in basic LDP discovery";
    }
  } // basic-discovery-timers

  grouping extended-discovery-timers {
    description
      "Extended discovery timer attributes.";
    leaf hello-holdtime {
      type uint16 {
        range 15..3600;
      }
      units seconds;
      default 45;
      description
        "The time interval for which LDP targeted Hello adjacency
        is maintained in the absence of targeted Hello messages
        from an LDP neighbor.";
    }
    leaf hello-interval {
      type uint16 {
        range 5..3600;
      }
      units seconds;
      default 15;
      description
        "The interval between consecutive LDP targeted Hello
        messages used in extended LDP discovery.";
    }        
  } // extended-discovery-timers

  grouping discovery-attributes-container {
    description
      "Dicscovery configuration attributes.";

    container discovery {
      description "Neibgbor discovery attributes.";
      
      container interfaces {
        description
          "Basic discovery attributes.";
        uses basic-discovery-timers;
      }
      
      container targeted
      {
        description
          "Extended discovery attributes.";
        uses extended-discovery-timers;
      } // targeted
    } // discovery
  } // discovery-attributes

  grouping graceful-restart-attributes {
    description
      "Graceful restart configuration attributes.";
    container graceful-restart {
      description 
        "Attributes for graceful restart.";      
      leaf enable {
        type boolean;
        description 
          "Enable or disable graceful restart.";
      }
      leaf helper-enable {
        if-feature graceful-restart-helper-mode;
        type boolean;
        description 
          "Enable or disable graceful restart helper mode.";
      }
      leaf reconnect-time {
        type uint16 {
          range 10..1800;
        }
        units seconds;
        description
          "Specifies the time interval that the remote LDP peer
          must wait for the local LDP peer to reconnect after the
          remote peer detects the LDP communication failure.";
      }
      leaf recovery-time {
        type uint16 {
          range 30..3600;
        }
        units seconds;
        description
          "";
      }
      leaf forwarding-holdtime {
        type uint16 {
          range 30..3600;
        }
        units seconds;
        description
          "";
      }
    } // graceful-restart
  } // graceful-restart-attributes

  grouping neighbor-attributes {
    description "Neighbor configuration attributes.";

    leaf session-ka-holdtime {
      type uint16 {
        range 45..3600;
      }
      units seconds;
      description
        "The time interval after which an inactive LDP session
        terminates and the corresponding TCP session closes.
        Inactivity is defined as not receiving LDP packets from the
        neighbor.";
    }
    leaf session-ka-interval {
      type uint16 {
        range 15..1200;
      }
      units seconds;
      description
        "The interval between successive transmissions of keepalive
        packets. Keepalive packets are only sent in the absence of
        other LDP packets transmitted over the LDP session.";
    }

    container session-protection {
      if-feature session-protection;
      description
        "Session protection attributes.";
      leaf enable {
        type boolean;
        description
          "'true' if session protection is enabled.";
      }
      leaf duration {
        type union {
          type uint32;
          type enumeration {
            enum "infinite" {
              description "The duration is infinite.";
            }                
          }
        }
        units seconds;
        description
          "Session protection duration.";
      }
    } // session-protection
  } // neighbor-attributes

  grouping neighbor-authentication {
    description
      "Neighbor authentication attributes.";
    leaf md5-password {      
      type string {
        length "1..80";
      }
      description
        "Assigns an encrypted MD5 password to an LDP
        neighbor";
    } // md5-password
  } // neighbor-authentication

  grouping neighbor-attributes-container {
    description "Container of neighbor configuration attributes.";
    container neighbors {
      description 
        "Container of neighbor configuration attributes.";
      uses neighbor-authentication {
        if-feature global-session-authentication;
      }
      uses neighbor-attributes;
    }
  } // neighbor-attributes-container

  grouping instance-attributes {
    description "Configuration attributes at instance level.";

    uses graceful-restart-attributes;

    leaf igp-synchronization-delay {
      type uint16 {
        range 3..60;
      }
      units seconds;
      description
        "Sets the interval that the LDP waits before notifying the
        Interior Gateway Protocol (IGP) that label exchange is
        completed so that IGP can start advertising the normal
        metric for the link.";
    }  
  } // instance-attributes
  
  grouping global-attributes {
    description "Configuration attributes at global level.";

    uses instance-attributes;

    leaf nonstop-routing {
      type boolean;
      default false;
      description
        "Enables Nonstop Routing (NSR)";
    }    
  } // global-attributes

  grouping policy-attributes {
    description
      "LDP policy attributes.";
    container label-policy {
      description
        "Label policy attributes.";
      container independent {
        description
          "Independent label policy attributes.";
        container assign {
          if-feature policy-label-assignment-config;
          description
            "Label assignment policies";
          choice prefix-option {
            description
              "Use either prefix-list or host-routes-only.";
            case prefix-list {
              leaf prefix-list {
                type prefix-list-ref;
                description
                  "Assign labels according to certain prefixes.";
              }
            }
            case host-routes-only {
              leaf host-routes-only {
                type boolean;
                description
                  "'true' to apply host routes only.";
              }
            }
          } // prefix-option
        }
        container advertise {
          description
            "Label advertising policies.";
          container explicit-null {
            presence "Present to enable explicit null.";
            description
              "Enables an egress router to advertise an
              explicit null label (value 0) in place of an
              implicit null label (value 3) to the
              penultimate hop router.";
            leaf prefix-list {
              type prefix-list-ref;
              description
                "Prefix list name. Applies the filters in the
                specified prefix list to label 
                advertisements.
                If the prefix list is not specified, explicit
                null label advertisement is enabled for all
                directly connected prefixes.";
            }
          }
          leaf prefix-list {
            type prefix-list-ref;
            description
              "Applies the prefix list to outgoing label
              advertisements.";
          }
        }
        container accept {
          description
            "Label advertisement acceptance policies.";
          leaf prefix-list {
            type prefix-list-ref;
            description
              "Applies the prefix list to incoming label
              advertisements.";
          }
        }
      } // independent
      container ordered {
        if-feature policy-ordered-label-config;
        description
          "Ordered label policy attributes.";
        container egress-lsr {
          description
            "Egress LSR label assignment policies";
          leaf prefix-list {
            type prefix-list-ref;
            description
              "Assign labels according to certain prefixes.";
          }
        }
        container advertise {
          description
            "Label advertising policies.";
          leaf prefix-list {
            type prefix-list-ref;
            description
              "Applies the prefix list to outgoing label
              advertisements.";
          }
        }
        container accept {
          description
            "Label advertisement acceptance policies.";
          leaf prefix-list {
            type prefix-list-ref;
            description
              "Applies the prefix list to incoming label
              advertisements.";
          }
        }
      } // ordered
    } // label-policy
  } // policy-attributes
  
  grouping neighbor-af-policy-attributes {
    description
      "LDP policy attributes under neighbor address-family.";
    container label-policy {
      description
        "Label policy attributes.";
      container advertise {
	description
	  "Label advertising policies.";
        container explicit-null {
          presence "Present to enable explicit null.";
          description
            "Enables an egress router to advertise an
            explicit null label (value 0) in place of an
            implicit null label (value 3) to the
            penultimate hop router.";
          leaf prefix-list {
            type prefix-list-ref;
            description
              "Prefix list name. Applies the filters in the
              specified prefix list to label 
              advertisements.
              If the prefix list is not specified, explicit
              null label advertisement is enabled for all
              directly connected prefixes.";
          }
        }
        leaf prefix-list {
          type prefix-list-ref;
            description
              "Applies the prefix list to outgoing label
              advertisements.";
        }
      }
      container accept {
        description
          "Label advertisement acceptance policies.";
        leaf prefix-list {
          type prefix-list-ref;
          description
            "Applies the prefix list to incoming label
            advertisements.";
        }
      } // accept
    } // label-policy
  } // neighbor-af-policy-attributes

  grouping extended-discovery-policy-attributes {
    description
      "LDP policy to control the acceptance of extended neighbor
      discovery hello messages.";
    container hello-accept {
      if-feature policy-extended-discovery-config;
      description
        "Extended discovery acceptance policies.";
      
      leaf enable {
        type boolean;
        description 
          "'true' to accept; 'false' to deny.";
      }
      leaf peer-list {
        type string;
        description
          "The name of a peer ACL.";
      }
    } // hello-accept
  } // extended-discovery-policy-attributes

  /*
   * Configuration data nodes
   */

  augment "/rt:routing/rt:routing-instance/rt:routing-protocols/"
    + "rt:routing-protocol" {
    when "rt:type = 'ldp:ldp'" {
      description
        "This augment is only valid for a protocol instance
        of LDP.";
    }
    description "LDP augmentation.";

    container ldp {
      description
        "LDP.";

      uses global-attributes;      
      uses discovery-attributes-container;
      uses neighbor-attributes-container;

      list instance {
        key "name";
        description
          "Per-vrf global params.";
        
        leaf name {
          type string;
          description
            "VRF instance name.";
        }

        leaf admin-down {
          type boolean;
          default false;
          description
            "'true' to disable the instance.";
        }

        leaf router-id {
          type union {
            type yang:dotted-quad;
            type uint32;
          }
          description "Router ID.";
        }

        container capability {
          if-feature capability-config;
          description "Configure capability.";
          leaf upstream-lbl-assignment {
            type boolean;
            description
              "Enable upstream label assignment.";
          }
          leaf end-of-lib {
            type boolean;
            description
              "Enable end-of-lib capability.";
          }
        } // capability

        uses instance-attributes;

        container address-family {
          description 
            "Per-vrf per-af params.";
          container ipv4 {
            description 
              "IPv4 address family.";
            leaf enable {
              type boolean;
              description
                "'true' to enable IPv4 address family.";
            }
            uses policy-attributes;
            leaf transport-address {
              type inet:ipv4-address;
              description
                "The transport address advertised in LDP Hello
                messages.";
            }
          } // ipv4
          container ipv6 {
            description 
              "IPv6 address family.";
            leaf enable {
              type boolean;
              description
                "'true' to enable IPv6 address family.";
            }
            uses policy-attributes;
            leaf transport-address {
              type inet:ipv6-address;
              description
                "The transport address advertised in LDP Hello
                messages.";
            }
          } // ipv6
        }

        container discovery {
          description
            "Neibgbor discovery configuration.";

          container interfaces {
            description
              "A list of interfaces for basic descovery.";
            uses basic-discovery-timers;

            list interface {
              key "interface";
              description
                "List of LDP interfaces.";
              leaf interface {
                type if:interface-ref;
                description
                  "Interface.";            
              }
              uses basic-discovery-timers {
                if-feature per-interface-timer-config;
              }

              container address-family {
                description 
                  "Per-vrf per-af params.";
                container ipv4 {
                  must "/if:interfaces/if:interface"
                    + "[name = current()/../../interface]/ip:ipv4" {
                    description
                      "Only if IPv4 is enabled on the interface.";
                  }
                  description 
                    "IPv4 address family.";
                  leaf transport-address {
                    type union {
                      type enumeration {
                        enum "use-interface-address" {
                          description 
                            "Use interface address as the transport
                            address.";
                        }
                      }                      
                      type inet:ipv4-address;
                    }
                    description
                      "IP address to be advertised as the LDP
                      transport address.";
                  }
                  leaf enable {
                    type boolean;
                    description
                      "Enable IPv4 address familyon the interface.";
                  }
                }
                container ipv6 {
                  must "/if:interfaces/if:interface"
                    + "[name = current()/../../interface]/ip:ipv6" {
                    description
                      "Only if IPv6 is enabled on the interface.";
                  }
                  description 
                    "IPv6 address family.";
                  leaf transport-address {
                    type union {
                      type enumeration {
                        enum "use-interface-address" {
                          description 
                            "Use interface address as the transport
                            address.";
                        }
                      }                      
                      type inet:ipv4-address;
                    }
                    description
                      "IP address to be advertised as the LDP
                      transport address.";
                  }
                  leaf enable {
                    type boolean;
                    description
                      "Enable IPv6 address familyon the interface.";
                  }
                } // ipv6
              } // address-family
            } // list interface
          } // interfaces
          
          container targeted
          {
            description
              "A list of targeted neighbors for extended discovery.";
            uses extended-discovery-timers;
            uses extended-discovery-policy-attributes;

            container address-family {
              description 
                "Per-vrf per-af params.";
              container ipv4 {
                description 
                  "IPv4 address family.";
                list target {
                  key "address";
                  description
                    "Targeted discovery params.";
              
                  leaf address {
                    type inet:ipv4-address;
                    description
                      "Configures a remote LDP neighbor and enables
                      extended LDP discovery of the specified
                      neighbor.";
                  }
                  leaf enable {
                    type boolean;
                    description
                      "Enable the target.";
                  }
                }
              } // ipv4
              container ipv6 {
                description 
                  "IPv6 address family.";
                list target {
                  key "address";
                  description
                    "Targeted discovery params.";
              
                  leaf address {
                    type inet:ipv6-address;
                    description
                      "Configures a remote LDP neighbor and enables
                      extended LDP discovery of the specified
                      neighbor.";
                  }
                  leaf enable {
                    type boolean;
                    description
                      "Enable the target.";
                  }
                }
              } // ipv6
            } // address-family
          } // targeted
        } // discovery

        container neighbors {
          description
            "Neighbors configuration attributes.";
          
          uses neighbor-authentication {
            if-feature global-session-authentication;
          }
          uses neighbor-attributes;

          list neighbor {
            key "lsr-id";
            description
              "List of neighbors.";
            
            leaf lsr-id {
              type union {
                type yang:dotted-quad;
                type uint32;
              }
              description "LSR ID.";
            }

            leaf admin-down {
              type boolean;
              default false;
              description
                "'true' to disable the neighbor.";
            }

            uses neighbor-authentication;
            
            uses graceful-restart-attributes {
              if-feature per-neighbor-graceful-restart-config;
            }

            uses neighbor-attributes {
              if-feature per-neighbor-session-attributes-config;
            }

            container address-family {
              description 
                "Per-vrf per-af params.";
              container ipv4 {
                description 
                  "IPv4 address family.";
		uses neighbor-af-policy-attributes;
              }
              container ipv6 {
                description 
                  "IPv6 address family.";
		uses neighbor-af-policy-attributes;
              } // ipv6
            } // address-family
          } // list neighbor
        } // neighbors        
      } // instance
    } // container ldp
  }

  /*
   * Operational state data nodes
   */

  augment "/rt:routing-state/rt:routing-instance/"
    + "rt:routing-protocols/rt:routing-protocol" {
    when "rt:type = 'ldp:ldp'"  {
      description
        "This augment is only valid for a protocol instance
        of type 'ldp'.";
    }
    description
      "LDP state.";
    container ldp {
      description "LDP";
      
    }
  }

  /*
   * RPCs
   */

  /*
   * Notifications
   */
  notification ldp-neighbor-event {
    description 
      "Notification event for a change of LDP neighbor operational
      status.";
    leaf event-type {
      type oper-status-event-type;
      description "Event type.";
    }
    uses ldp-neighbor-ref;
  }

  notification ldp-adjacency-event {
    description 
      "Notification event for a change of LDP adjacency operational
      status.";
    leaf event-type {
      type oper-status-event-type;
      description "Event type.";
    }
    uses ldp-interface-ref;
  }  
}
